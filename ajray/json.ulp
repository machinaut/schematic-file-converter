// json.ulp - Export an EagleCAD file into JSON
// Generated by the codez in this wonderful github repo:
// http://github.com/ajray/schematic-file-converter
// Alex Ray (2011) <ajray@ncsu.edu>
string esc(string s) { // JSON string escapes
    string out = "\""; // open quote
    for (int i = 0; s[i]; ++i) {
        switch(s[i]) {
            case '"': out += "\""; break;
            case '\\': out += "\\\\"; break;
            case '/': out += "\\/"; break;
            case '\b': out += "\\b"; break;
            case '\f': out += "\\f"; break;
            case '\n': out += "\\n"; break;
            case '\r': out += "\\r"; break;
            case '\t': out += "\\t"; break;
            default: out += s[i];
        }
    }
    out += "\""; // close quote
    return out;
}
void n()          { printf("\n"); }     // newline
void cn()         { printf(",\n"); }    // comma & newline
void po(string a) { printf("%s:{",a); } // start of an object
void on()         { printf("}"); }      // end of an object
void pl(string a) { printf("%s:[",a); } // start of a list
void ln()         { printf("]"); }      // end of a list
void print_string (string a, string b)  { printf("%s:%s",a,esc(b)); }
void print_int    (string a, int b)     { printf("%s:%d",a,b); }
void print_real   (string a, real b)    { printf("%s:%g",esc(a),b); }
void print_layer(UL_LAYER layer) { po("layer");
	print_int("used",layer.used); cn();
	print_string("name",layer.name); cn();
	print_int("color",layer.color); cn();
	print_int("number",layer.number); cn();
	print_int("visible",layer.visible); cn();
	print_int("fill",layer.fill); on();}
void print_via(UL_VIA via) { po("via");
	print_int("diameter",via.diameter); cn();
	print_int("end",via.end); cn();
	print_int("start",via.start); cn();
	print_int("shape",via.shape); cn();
	print_int("drillsymbol",via.drillsymbol); cn();
	print_int("drill",via.drill); cn();
	print_int("x",via.x); cn();
	print_int("y",via.y); cn();
	print_int("flags",via.flags); on();}
void print_pin(UL_PIN pin) { po("pin");
	print_circles("circles",pin.circles); cn();
	print_real("function",pin.function); cn();
	print_real("direction",pin.direction); cn();
	print_real("angle",pin.angle); cn();
	print_real("name",pin.name); cn();
	print_texts("texts",pin.texts); cn();
	print_real("visible",pin.visible); cn();
	print_int("y",pin.y); cn();
	print_instance("instances",pin.instances); cn();
	print_real("length",pin.length); cn();
	print_contact("contact",pin.contact); cn();
	print_real("swaplevel",pin.swaplevel); cn();
	print_int("x",pin.x); cn();
	print_real("net",pin.net); on();}
void print_attribute(UL_ATTRIBUTE attribute) { po("attribute");
	print_int("constant",attribute.constant); cn();
	print_string("name",attribute.name); cn();
	print_text("text",attribute.text); cn();
	print_string("defaultvalue",attribute.defaultvalue); cn();
	print_string("value",attribute.value); cn();
	print_int("display",attribute.display); on();}
void print_frame(UL_FRAME frame) { po("frame");
	print_int("y2",frame.y2); cn();
	print_int("layer",frame.layer); cn();
	print_int("rows",frame.rows); cn();
	print_int("y1",frame.y1); cn();
	print_text("texts",frame.texts); cn();
	print_wire("wires",frame.wires); cn();
	print_int("x2",frame.x2); cn();
	print_int("x1",frame.x1); cn();
	print_int("border",frame.border); cn();
	print_int("columns",frame.columns); on();}
void print_library(UL_LIBRARY library) { po("library");
	print_layers("layers",library.layers); cn();
	print_string("description",library.description); cn();
	print_string("headline",library.headline); cn();
	print_device("devices",library.devices); cn();
	print_symbol("symbols",library.symbols); cn();
	print_deviceset("devicesets",library.devicesets); cn();
	print_grid("grid",library.grid); cn();
	print_package("packages",library.packages); cn();
	print_string("name",library.name); on();}
void print_arc(UL_ARC arc) { po("arc");
	print_int("layer",arc.layer); cn();
	print_int("y2",arc.y2); cn();
	print_int("y1",arc.y1); cn();
	print_int("xc",arc.xc); cn();
	print_int("yc",arc.yc); cn();
	print_int("cap",arc.cap); cn();
	print_int("width",arc.width); cn();
	print_int("radius",arc.radius); cn();
	print_real("angle2",arc.angle2); cn();
	print_int("x2",arc.x2); cn();
	print_real("angle1",arc.angle1); cn();
	print_int("x1",arc.x1); on();}
void print_wire(UL_WIRE wire) { po("wire");
	print_int("style",wire.style); cn();
	print_int("y2",wire.y2); cn();
	print_int("y1",wire.y1); cn();
	print_int("cap",wire.cap); cn();
	print_real("curve",wire.curve); cn();
	print_int("layer",wire.layer); cn();
	print_wire("pieces",wire.pieces); cn();
	print_int("width",wire.width); cn();
	print_arc("arc",wire.arc); cn();
	print_int("x2",wire.x2); cn();
	print_int("x1",wire.x1); on();}
void print_sheet(UL_SHEET sheet) { po("sheet");
	print_circle("circles",sheet.circles); cn();
	print_wire("wires",sheet.wires); cn();
	print_area("area",sheet.area); cn();
	print_rectangle("rectangles",sheet.rectangles); cn();
	print_text("texts",sheet.texts); cn();
	print_int("number",sheet.number); cn();
	print_part("parts",sheet.parts); cn();
	print_bus("busses",sheet.busses); cn();
	print_frame("frames",sheet.frames); cn();
	print_net("nets",sheet.nets); cn();
	print_polygon("polygons",sheet.polygons); on();}
void print_polygon(UL_POLYGON polygon) { po("polygon");
	print_int("layer",polygon.layer); cn();
	print_int("rank",polygon.rank); cn();
	print_wire("fillings",polygon.fillings); cn();
	print_int("spacing",polygon.spacing); cn();
	print_int("orphans",polygon.orphans); cn();
	print_int("isolate",polygon.isolate); cn();
	print_int("pour",polygon.pour); cn();
	print_int("width",polygon.width); cn();
	print_wire("wires",polygon.wires); cn();
	print_wire("contours",polygon.contours); cn();
	print_int("thermals",polygon.thermals); on();}
void print_area(UL_AREA area) { po("area");
	print_int("x2",area.x2); cn();
	print_int("y1",area.y1); cn();
	print_int("x1",area.x1); cn();
	print_int("y2",area.y2); on();}
void print_label(UL_LABEL label) { po("label");
	print_int("layer",label.layer); cn();
	print_wire("wires",label.wires); cn();
	print_real("angle",label.angle); cn();
	print_text("text",label.text); cn();
	print_int("xref",label.xref); cn();
	print_int("mirror",label.mirror); cn();
	print_int("y",label.y); cn();
	print_int("x",label.x); cn();
	print_int("spin",label.spin); on();}
void print_instance(UL_INSTANCE instance) { po("instance");
	print_gate("gate",instance.gate); cn();
	print_gate("xrefs",instance.xrefs); cn();
	print_real("angle",instance.angle); cn();
	print_string("name",instance.name); cn();
	print_string("column",instance.column); cn();
	print_string("value",instance.value); cn();
	print_int("y",instance.y); cn();
	print_text("texts",instance.texts); cn();
	print_int("x",instance.x); cn();
	print_int("mirror",instance.mirror); cn();
	print_string("smashed",instance.smashed); cn();
	print_attribute("attributes",instance.attributes); cn();
	print_string("sheet",instance.sheet); cn();
	print_string("row",instance.row); on();}
void print_pad(UL_PAD pad) { po("pad");
	print_int("diameter",pad.diameter); cn();
	print_real("angle",pad.angle); cn();
	print_string("name",pad.name); cn();
	print_string("signal",pad.signal); cn();
	print_int("elongation",pad.elongation); cn();
	print_int("shape",pad.shape); cn();
	print_int("drillsymbol",pad.drillsymbol); cn();
	print_int("drill",pad.drill); cn();
	print_int("x",pad.x); cn();
	print_int("y",pad.y); cn();
	print_int("flags",pad.flags); on();}
void print_board(UL_BOARD board) { po("board");
	print_circle("circles",board.circles); cn();
	print_layer("layers",board.layers); cn();
	print_element("elements",board.elements); cn();
	print_string("name",board.name); cn();
	print_area("area",board.area); cn();
	print_hole("holes",board.holes); cn();
	print_wire("wires",board.wires); cn();
	print_library("libraries",board.libraries); cn();
	print_text("texts",board.texts); cn();
	print_class("classes",board.classes); cn();
	print_grid("grid",board.grid); cn();
	print_signal("signals",board.signals); cn();
	print_frame("frames",board.frames); cn();
	print_attribute("attributes",board.attributes); cn();
	print_rectangle("rectangles",board.rectangles); cn();
	print_polygon("polygons",board.polygons); on();}
void print_schematic(UL_SCHEMATIC schematic) { po("schematic");
	print_layer("layers",schematic.layers); cn();
	print_string("name",schematic.name); cn();
	print_part("parts",schematic.parts); cn();
	print_library("libraries",schematic.libraries); cn();
	print_class("classes",schematic.classes); cn();
	print_grid("grid",schematic.grid); cn();
	print_sheet("sheets",schematic.sheets); cn();
	print_string("xreflabel",schematic.xreflabel); cn();
	print_attribute("attributes",schematic.attributes); cn();
	print_net("nets",schematic.nets); on();}
void print_text(UL_TEXT text) { po("text");
	print_int("x",text.x); cn();
	print_int("layer",text.layer); cn();
	print_int("ratio",text.ratio); cn();
	print_string("value",text.value); cn();
	print_int("mirror",text.mirror); cn();
	print_int("y",text.y); cn();
	print_real("angle",text.angle); cn();
	print_int("font",text.font); cn();
	print_int("spin",text.spin); cn();
	print_int("size",text.size); on();}
void print_gate(UL_GATE gate) { po("gate");
	print_string("name",gate.name); cn();
	print_symbol("symbol",gate.symbol); cn();
	print_int("y",gate.y); cn();
	print_int("x",gate.x); cn();
	print_int("swaplevel",gate.swaplevel); cn();
	print_int("addlevel",gate.addlevel); on();}
void print_net(UL_NET net) { po("net");
	print_pinref("pinrefs",net.pinrefs); cn();
	print_string("name",net.name); cn();
	print_string("column",net.column); cn();
	print_segment("segments",net.segments); cn();
	print_class("class",net.class); cn();
	print_string("row",net.row); on();}
void print_smd(UL_SMD smd) { po("smd");
	print_int("layer",smd.layer); cn();
	print_real("angle",smd.angle); cn();
	print_string("name",smd.name); cn();
	print_string("signal",smd.signal); cn();
	print_int("y",smd.y); cn();
	print_int("flags",smd.flags); cn();
	print_int("dx",smd.dx); cn();
	print_int("dy",smd.dy); cn();
	print_int("roundness",smd.roundness); cn();
	print_int("x",smd.x); on();}
void print_symbol(UL_SYMBOL symbol) { po("symbol");
	print_circle("circles",symbol.circles); cn();
	print_wire("wires",symbol.wires); cn();
	print_string("name",symbol.name); cn();
	print_area("area",symbol.area); cn();
	print_text("texts",symbol.texts); cn();
	print_string("library",symbol.library); cn();
	print_pin("pins",symbol.pins); cn();
	print_frame("frames",symbol.frames); cn();
	print_rectangle("rectangles",symbol.rectangles); cn();
	print_polygon("polygons",symbol.polygons); on();}
void print_rectangle(UL_RECTANGLE rectangle) { po("rectangle");
	print_int("layer",rectangle.layer); cn();
	print_int("y2",rectangle.y2); cn();
	print_real("angle",rectangle.angle); cn();
	print_int("y1",rectangle.y1); cn();
	print_int("x2",rectangle.x2); cn();
	print_int("x1",rectangle.x1); on();}
void print_junction(UL_JUNCTION junction) { po("junction");
	print_int("y",junction.y); cn();
	print_int("diameter",junction.diameter); cn();
	print_int("x",junction.x); on();}
void print_bus(UL_BUS bus) { po("bus");
	print_segment("segments",bus.segments); cn();
	print_string("name",bus.name); on();}
void print_class(UL_CLASS class) { po("class");
	print_int("width",class.width); cn();
	print_int("clearance",class.clearance); cn();
	print_string("name",class.name); cn();
	print_int("drill",class.drill); cn();
	print_int("number",class.number); on();}
void print_part(UL_PART part) { po("part");
	print_string("name",part.name); cn();
	print_deviceset("deviceset",part.deviceset); cn();
	print_string("attribute",part.attribute); cn();
	print_string("value",part.value); cn();
	print_instance("instances",part.instances); cn();
	print_device("device",part.device); cn();
	print_attribute("attributes",part.attributes); on();}
void print_grid(UL_GRID grid) { po("grid");
	print_int("dots",grid.dots); cn();
	print_int("on",grid.on); cn();
	print_real("distace",grid.distace); cn();
	print_int("multiple",grid.multiple); cn();
	print_string("unit",grid.unit); cn();
	print_string("unitdist",grid.unitdist); on();}
void print_pinref(UL_PINREF pinref) { po("pinref");
	print_instance("instance",pinref.instance); cn();
	print_part("part",pinref.part); cn();
	print_pin("pin",pinref.pin); on();}
void print_device(UL_DEVICE device) { po("device");
	print_gate("gates",device.gates); cn();
	print_string("description",device.description); cn();
	print_area("area",device.area); cn();
	print_string("headline",device.headline); cn();
	print_package("package",device.package); cn();
	print_string("library",device.library); cn();
	print_string("prefix",device.prefix); cn();
	print_string("value",device.value); cn();
	print_attribute("attributes",device.attributes); cn();
	print_string("technologies",device.technologies); cn();
	print_string("name",device.name); on();}
void print_hole(UL_HOLE hole) { po("hole");
	print_int("y",hole.y); cn();
	print_int("diameter",hole.diameter); cn();
	print_int("drillsymbol",hole.drillsymbol); cn();
	print_int("drill",hole.drill); cn();
	print_int("x",hole.x); on();}
void print_segment(UL_SEGMENT segment) { po("segment");
	print_text("texts",segment.texts); cn();
	print_wire("wires",segment.wires); cn();
	print_label("labels",segment.labels); cn();
	print_pinref("pinrefs",segment.pinrefs); cn();
	print_junction("junctions",segment.junctions); on();}
void print_circle(UL_CIRCLE circle) { po("circle");
	print_int("y",circle.y); cn();
	print_int("width",circle.width); cn();
	print_int("layer",circle.layer); cn();
	print_int("radius",circle.radius); cn();
	print_int("x",circle.x); on();}
void print_contactref(UL_CONTACTREF contactref) { po("contactref");
	print_contact("contact",contactref.contact); cn();
	print_element("element",contactref.element); on();}
void print_package(UL_PACKAGE package) { po("package");
	print_wire("wires",package.wires); cn();
	print_string("description",package.description); cn();
	print_contact("contacts",package.contacts); cn();
	print_string("headline",package.headline); cn();
	print_circle("cicles",package.cicles); cn();
	print_hole("holes",package.holes); cn();
	print_string("library",package.library); cn();
	print_area("area",package.area); cn();
	print_frame("frames",package.frames); cn();
	print_text("texts",package.texts); cn();
	print_rectangle("rectangles",package.rectangles); cn();
	print_polygon("polygons",package.polygons); cn();
	print_string("name",package.name); on();}
void print_signal(UL_SIGNAL signal) { po("signal");
	print_wire("wires",signal.wires); cn();
	print_string("name",signal.name); cn();
	print_class("class",signal.class); cn();
	print_via("vias",signal.vias); cn();
	print_contactref("contactrefs",signal.contactrefs); cn();
	print_int("airwireshidden",signal.airwireshidden); cn();
	print_polygon("polygons",signal.polygons); on();}
void print_deviceset(UL_DEVICESET deviceset) { po("deviceset");
	print_gate("gates",deviceset.gates); cn();
	print_string("description",deviceset.description); cn();
	print_area("area",deviceset.area); cn();
	print_string("headline",deviceset.headline); cn();
	print_string("library",deviceset.library); cn();
	print_string("prefix",deviceset.prefix); cn();
	print_device("devices",deviceset.devices); cn();
	print_string("value",deviceset.value); cn();
	print_string("name",deviceset.name); on();}
void print_element(UL_ELEMENT element) { po("element");
	print_int("x",element.x); cn();
	print_real("angle",element.angle); cn();
	print_string("name",element.name); cn();
	print_package("package",element.package); cn();
	print_string("column",element.column); cn();
	print_string("attribute",element.attribute); cn();
	print_string("value",element.value); cn();
	print_int("y",element.y); cn();
	print_text("texts",element.texts); cn();
	print_int("mirror",element.mirror); cn();
	print_int("smashed",element.smashed); cn();
	print_int("locked",element.locked); cn();
	print_attribute("attributes",element.attributes); cn();
	print_int("spin",element.spin); cn();
	print_string("row",element.row); on();}
void print_contact(UL_CONTACT contact) { po("contact");
	print_string("string",contact.string); cn();
	print_string("signal",contact.signal); cn();
	print_pad("pad",contact.pad); cn();
	print_int("y",contact.y); cn();
	print_int("x",contact.x); cn();
	print_smd("smd",contact.smd); on();}
